# xcom-t025-sanitized requirements

# Specification: xcom-t025-sanitized requirements

## T025-SR-001
The authority must accept a finite set of declared clock domain identities and must report an unknown or undeclared domain as a distinct deterministic failure.
- Revision: 1
- Level: software
- Status: accepted
- Source: {"kind": "admitted_packet_and_bridge", "reference": "packet.md (time authority identifies clock domains); interface-bridge.md; anchors: XVE-SYS-0147, FR-015"}
- Applicability: xverse::xcom::validation:: time authority public API; C++20 stdlib only.
- VerificationIntent: Unit: register and query declared domains; query an undeclared domain and assert the UnknownClock outcome with unchanged authority state.
- AcceptanceCriteria: A declared domain is accepted and addressable by identity.
  An undeclared domain yields a distinct UnknownClock result and no state mutation.
  Domain identity is stable across calls and supports equality comparison.

## T025-SR-002
The authority must obtain current time for a declared domain from a host-supplied time source within a bounded, explicit interval, and must report failure distinctly when the source is unavailable or returns an out-of-bounds value.
- Revision: 1
- Level: software
- Status: accepted
- Source: {"kind": "admitted_packet_and_bridge", "reference": "packet.md (obtains bounded current time); interface-bridge.md; anchors: XVE-SYS-0147, FR-015"}
- Applicability: xverse::xcom::validation time authority; deterministic injectable source for tests.
- VerificationIntent: Unit: inject a deterministic source and assert domain attribution; inject failure and out-of-bounds sources and assert distinct failures.
- AcceptanceCriteria: A valid read returns a timestamp attributed to the requested domain only.
  A source failure or out-of-bounds value yields a distinct deterministic failure, not a guessed value.
  Reads never fabricate time nor silently fall back to another domain.

## T025-SR-003
Converting a time from a source domain to a destination domain must require a declared mapping carrying source, destination, and maximum admissible tolerance; a missing mapping or a tolerance failure must return distinct deterministic results.
- Revision: 1
- Level: software
- Status: accepted
- Source: {"kind": "admitted_packet_and_bridge", "reference": "packet.md (maps between domains only under declared source, destination, and tolerance rules); interface-bridge.md; anchors: XVE-SYS-0147, FR-015"}
- Applicability: xverse::xcom::validation time authority mapping table; finite host-configurable bound.
- VerificationIntent: Unit: declared mapping inside, at, and beyond tolerance; reverse-direction request; undeclared pair; assert distinct outcomes and no mutation.
- AcceptanceCriteria: A declared mapping converts within tolerance and reports the destination domain.
  An undeclared source-to-destination pair yields a distinct MissingMapping result.
  A conversion beyond the declared tolerance yields a distinct tolerance-failure result.
  Mappings are directional: a declared A-to-B mapping does not silently enable B-to-A.

## T025-SR-004
The authority must detect monotonic regression in a domain and arithmetic overflow during conversion, and must return distinct deterministic results for each.
- Revision: 1
- Level: software
- Status: accepted
- Source: {"kind": "admitted_packet_and_bridge", "reference": "packet.md (regression and overflow produce distinct deterministic results); interface-bridge.md; anchors: XVE-SYS-0147, FR-015"}
- Applicability: xverse::xcom::validation time authority; deterministic arithmetic checks.
- VerificationIntent: Unit: sequence decreasing readings; construct a boundary conversion that overflows; assert distinct codes and unchanged state.
- AcceptanceCriteria: A reading earlier than a prior reading in the same declared monotonic domain yields a distinct regression result.
  A conversion whose result cannot be represented yields a distinct overflow result.
  Regression and overflow are distinguishable from tolerance failure and from each other.

## T025-SR-005
Permit-validity and session-lifecycle time decisions must be expressed as authority queries in a single domain or through a declared mapping; raw timestamps from different domains must never be compared directly.
- Revision: 1
- Level: software
- Status: accepted
- Source: {"kind": "admitted_packet_and_bridge", "reference": "packet.md (raw timestamps from different domains are never compared); interface-bridge.md; anchors: FR-015, FR-033, XVE-SYS-0147"}
- Applicability: xverse::xcom::validation permit validity and session lifecycle time checks.
- VerificationIntent: Unit: valid and expired permit in-domain; permit expressed in a foreign domain with and without a mapping; static check that direct cross-domain comparison is absent.
- AcceptanceCriteria: Every time-dependent decision path resolves its comparison through the authority.
  A permit whose validity interval is in another domain is evaluated only after a successful declared mapping, otherwise rejected with MissingMapping.
  No code path directly compares two raw timestamps from different domains.

## T025-SR-006
The time authority must be non-copyable, must have an explicit documented lifetime, and must be safe for concurrent read/query use with deterministic results.
- Revision: 1
- Level: software
- Status: accepted
- Source: {"kind": "admitted_packet_and_bridge", "reference": "packet.md (define synchronization and lifetime rules, including whether the authority is non-copyable); interface-bridge.md REF-002; anchors: XVE-SYS-0147, FR-033"}
- Applicability: xverse::xcom::validation time authority ownership contract; strict Doxygen required.
- VerificationIntent: Unit and static: non-copyability assertion; concurrent query test; strict Doxygen build for the documented ownership/lifetime/thread-safety contract.
- AcceptanceCriteria: Copy construction and copy assignment of the authority are not available.
  The public API documents ownership, lifetime, and thread-safety guarantees.
  Concurrent queries from multiple threads return deterministic results with no data race under the applicable sanitizer check.

## T025-SR-007
A permit must be immutable once constructed and must bind exactly one session identity, plan digest, scenario, deployment, environment, tool, interface, target, nonce, allowed action set, validity interval, and every finite quota or capacity.
- Revision: 1
- Level: software
- Status: accepted
- Source: {"kind": "admitted_packet_and_bridge", "reference": "packet.md (the immutable permit binds exactly one session identity, plan digest, ... every finite quota or capacity); interface-bridge.md REF-002; anchors: XVE-SYS-0152, XVE-SYS-0144, FR-016"}
- Applicability: xverse::xcom::validation immutable permit value type; no mutator exposed.
- VerificationIntent: Unit: field-by-field mismatch matrix, one test per bound field, asserting rejection and the identified mismatching field; mutability absence asserted by API shape.
- AcceptanceCriteria: All listed fields are present, immutable, and individually comparable; the permit exposes no mutator.
  A mismatch in any single field between permit and consuming session is detected and the field is identifiable.
  Absent or default-initialised values for an identity-bearing field are rejected and never treated as a wildcard.

## T025-SR-008
The allowed action set must be a closed, finite set; undefined action bits and composite values not explicitly allowed must be rejected deterministically.
- Revision: 1
- Level: software
- Status: accepted
- Source: {"kind": "admitted_packet_and_bridge", "reference": "packet.md (reject undefined action bits or composite values that are not explicitly allowed); interface-bridge.md REF-002; anchors: FR-016"}
- Applicability: xverse::xcom::validation permit action-set validation.
- VerificationIntent: Unit: allowed single action; undefined bit; disallowed combination; assert distinct codes and no partial acceptance.
- AcceptanceCriteria: A permitted single action within the allowed set succeeds at validation.
  An undefined action bit is rejected with a distinct code.
  A composite or combined value not declared allowed is rejected with a distinct code and never interpreted as its components.

## T025-SR-009
Consumption must be controller-scoped and exactly-once: a consumed permit identity, or a session identity already bound to a consumed permit, must not be consumed again, including when presented with a changed nonce.
- Revision: 1
- Level: software
- Status: accepted
- Source: {"kind": "admitted_packet_and_bridge", "reference": "packet.md (define a global or controller-scoped one-time-consumption rule; prevent duplicate exact permit or session identity from being consumed twice, including with a changed nonce); interface-bridge.md REF-002; anchors: XVE-SYS-0152, XVE-SYS-0144, FR-017"}
- Applicability: xverse::xcom::validation controller-scoped consumption bookkeeping; finite bound.
- VerificationIntent: Unit: replay matrix (same permit/same nonce, same permit/changed nonce, different session/same permit); concurrent double consumption; assert exactly one success.
- AcceptanceCriteria: First consumption of a valid permit succeeds and records the binding atomically.
  Re-presenting the same permit identity is rejected, including with a different nonce.
  A different session identity presenting an already-consumed permit identity is rejected.
  Attempts to consume a permit already bound to another session identity are rejected.
  The declared replay scope (per controller instance) is documented and enforced.

## T025-SR-010
Every finite quota or capacity bound carried by the permit and every bounded bookkeeping structure must have an explicit exhaustion result and must never exceed its bound.
- Revision: 1
- Level: software
- Status: accepted
- Source: {"kind": "admitted_packet_and_bridge", "reference": "packet.md (return explicit exhaustion behavior; every finite quota or capacity); interface-bridge.md REF-002; anchors: XVE-SYS-0152, FR-017"}
- Applicability: xverse::xcom::validation permit quotas and controller bookkeeping bounds; finite host-configurable.
- VerificationIntent: Unit and boundary: capacity-1 and capacity-N boundaries for quotas and for session/permit tables; assert last-success and first-exhaustion results.
- AcceptanceCriteria: Consuming at the final available unit succeeds; one beyond yields a distinct exhaustion result.
  Exhaustion does not consume, partially apply, or mutate unrelated state.
  Bookkeeping structures never grow past their configured bound.

## T025-SR-011
A session handle must bind a host-generated controller identity and a generation counter so that stale, foreign, and recreated-controller handles cannot authorise any operation.
- Revision: 1
- Level: software
- Status: accepted
- Source: {"kind": "admitted_packet_and_bridge", "reference": "packet.md (session handles bind a host-generated controller identity and generation so stale, foreign, and recreated-controller handles cannot authorize a record); interface-bridge.md REF-002; anchors: XVE-SYS-0144, XVE-SYS-0152, FR-018"}
- Applicability: xverse::xcom::validation session handle and controller identity types.
- VerificationIntent: Unit: ownership and recreation matrix with stale, foreign, and forged handles; assert rejection, no mutation, and no effect on any other live session.
- AcceptanceCriteria: A valid current handle from the owning controller is accepted.
  A stale handle (prior generation) is rejected distinctly.
  A foreign handle (different controller identity) is rejected distinctly.
  A handle from a recreated controller with the same name but a new identity is rejected.
  Handle forgery never addresses a live session.

## T025-SR-012
The lifecycle must expose declared to armed to active to closing to closed, with expired, revoked, and evidence-incomplete as terminal states, and must define which transitions are legal from each state.
- Revision: 1
- Level: software
- Status: accepted
- Source: {"kind": "admitted_packet_and_bridge", "reference": "packet.md (the lifecycle exposes declared, armed, active, closing, closed; expired, revoked, and evidence-incomplete are terminal); interface-bridge.md REF-002; anchors: XVE-SYS-0152, FR-018"}
- Applicability: xverse::xcom::validation session state machine.
- VerificationIntent: Unit: full transition table (legal and illegal pairs); terminal-state lockout; assert resulting state values and rejection codes.
- AcceptanceCriteria: Each state is reachable via its defined operation from its predecessor.
  Terminal states admit no outgoing transition and attempts are rejected deterministically.
  Invalid transitions such as declared to active are rejected without mutation.
  Expiry and revocation can be applied from the states where they are legal.

## T025-SR-013
Validation of handle, context, time, and action must complete before any state mutation; safe idempotent repeats must be accepted with a stable already-applied outcome and unsafe repeats must be rejected.
- Revision: 1
- Level: software
- Status: accepted
- Source: {"kind": "admitted_packet_and_bridge", "reference": "packet.md (define safe idempotency, reject unsafe repeats, and ensure validation of handle, context, time, and action precedes any state mutation); interface-bridge.md REF-002; anchors: XVE-SYS-0144, FR-019"}
- Applicability: xverse::xcom::validation session transition operations.
- VerificationIntent: Unit: each pre-mutation validation stage injected in turn with a state snapshot comparison; safe-repeat and unsafe-repeat cases for each transition.
- AcceptanceCriteria: No state change is observable when any pre-mutation validation fails.
  A safe repeat (already in the requested state with the same owning handle) returns a stable already-applied outcome without changing state.
  An unsafe repeat conflicting with current state is rejected distinctly.
  The set of safe repeats is explicitly enumerated in the design.

## T025-SR-014
Live session capacity and controller/handle bookkeeping must be finite and host-configurable; creation beyond capacity must fail explicitly without leaking a handle.
- Revision: 1
- Level: software
- Status: accepted
- Source: {"kind": "admitted_packet_and_bridge", "reference": "packet.md (finite quotas or capacities; bounded session lifecycle); interface-bridge.md REF-002; anchors: XVE-SYS-0147, FR-033"}
- Applicability: xverse::xcom::validation session table and slot accounting; finite host-configurable bound.
- VerificationIntent: Unit and boundary: fill to capacity, attempt overflow, close one, reuse; assert results, handle invalidity, and slot accounting.
- AcceptanceCriteria: Creating sessions up to capacity succeeds; one beyond yields an explicit capacity result.
  A failed creation returns no usable handle and leaves capacity unchanged.
  Closing or terminating a session frees exactly its capacity slot, allowing reuse.

## T025-SR-015
Every rejected operation must leave the affected session record, permit consumption bookkeeping, counters, and authority state unchanged.
- Revision: 1
- Level: software
- Status: accepted
- Source: {"kind": "admitted_packet_and_bridge", "reference": "packet.md (rejected operations leave state unchanged); interface-bridge.md REF-002; anchors: XVE-SYS-0154, FR-019"}
- Applicability: xverse::xcom::validation all rejecting operations.
- VerificationIntent: Unit: snapshot-before/after assertions for every negative case in the mismatch, replay, clock, handle, and lifecycle matrices.
- AcceptanceCriteria: For each negative case a snapshot-equality assertion covers state, consumed set, and counters.
  Rejection on one session does not perturb any other session or the authority.
  A failed transition never partially applies and exposes no intermediate state.

## T025-SR-016
Diagnostics must be returned as an ordered sequence of stable, enumerable codes with no payload, item, observation, or free-form content, and multi-failure ordering must follow a declared precedence.
- Revision: 1
- Level: software
- Status: accepted
- Source: {"kind": "admitted_packet_and_bridge", "reference": "packet.md (produce stable, ordered, payload-free diagnostics); interface-bridge.md REF-002; anchors: XVE-SYS-0154, FR-020"}
- Applicability: xverse::xcom::validation public diagnostic result type.
- VerificationIntent: Unit: precedence cases with an expected exact code sequence; repeat determinism; structural assertion that diagnostic types hold no payload.
- AcceptanceCriteria: A diagnostic value is a bounded enumerable code, optionally with a bounded numeric locator, and carries no data string.
  Multi-failure inputs produce the declared precedence order, identical on repetition.
  The same input yields the same code sequence across runs and builds.
  No diagnostic can carry a communication item, observation, or payload.

## T025-SR-017
Concurrent permit consumption and concurrent session mutation must be atomic with respect to shared state, producing deterministic outcomes with exactly one success where the operation is exactly-once.
- Revision: 1
- Level: software
- Status: accepted
- Source: {"kind": "admitted_packet_and_bridge", "reference": "packet.md (explicit time authority; deterministic concurrency; synchronization rules); interface-bridge.md REF-002; anchors: XVE-SYS-0147, FR-033"}
- Applicability: xverse::xcom::validation shared controller and consumption state.
- VerificationIntent: Unit and integration: multithreaded consumption and lifecycle stress with an exact success-count assertion and sanitizer execution.
- AcceptanceCriteria: N concurrent consumptions of one valid permit yield exactly one success.
  The remaining N-minus-1 outcomes are drawn from the defined non-success set with no duplicate applied mutation.
  Shared mutable state is guarded so no data race is reported under the applicable sanitizer run.

## T025-SR-018
The candidate must not expose or perform any normal-route emission: no communication item, transport, gateway, network listener, journal, lease, dashboard, persistent store, or external service, and no logging or telemetry in the nominal path.
- Revision: 1
- Level: software
- Status: accepted
- Source: {"kind": "admitted_packet", "reference": "packet.md (the foundation must neither emit a communication item nor create a transport, gateway, network listener, journal, lease, dashboard, persistent store, or external service; all normal-route emission counts remain zero); anchors: FR-020"}
- Applicability: xverse::xcom::validation public API surface and nominal execution path.
- VerificationIntent: Static: API-surface enumeration and I/O-call inspection. Unit and integration: nominal scenario asserting a zero emission counter and absence of emission side effects.
- AcceptanceCriteria: The public API surface contains no emission, transport, or persistence entry point.
  Nominal operations perform no file, socket, or environment I/O.
  A reported normal-route emission counter is zero after the nominal test scenario.

## T025-STK-001
All permit-validity and session-lifecycle time decisions must be made through a single explicit time authority that knows its clock domains and only compares times within one domain or through a declared mapping.
- Revision: 1
- Level: stakeholder
- Status: accepted
- Source: {"kind": "admitted_packet_and_bridge", "reference": "packet.md (time-authority clause); interface-bridge.md; anchors: XVE-SYS-0147, FR-015, FR-033"}
- Applicability: T025 standalone candidate: xverse::xcom::validation, C++20 standard library only; foundation slice, no stimulation.
- VerificationIntent: Preserve as the top-level intent refined by T025-SR-001..T025-SR-005; verified through their unit and static checks.
- AcceptanceCriteria: AC-1: No code path compares a raw timestamp from one clock domain with a raw timestamp from a different clock domain.
  AC-2: An unrecognised clock domain yields a distinct deterministic result rather than silent success.
  AC-3: A cross-domain comparison without a declared mapping yields a distinct deterministic result rather than silent success.
  AC-4: Unknown clock, missing mapping, tolerance failure, regression, and overflow are each distinguishable by result value.

## T025-STK-002
A host-controlled local validation permit must bind exactly one session and its complete operational envelope, and must be consumed at most once.
- Revision: 1
- Level: stakeholder
- Status: accepted
- Source: {"kind": "admitted_packet_and_bridge", "reference": "packet.md (immutable permit / one-time consumption clause); interface-bridge.md REF-002; anchors: XVE-SYS-0152, XVE-SYS-0144, FR-016, FR-017"}
- Applicability: T025 standalone candidate; local prototype permit control only, general channel identity/access deferred to Security.
- VerificationIntent: Refined by T025-SR-007..T025-SR-010 and verified by the permit mismatch, replay, action-set, and exhaustion matrices.
- AcceptanceCriteria: AC-1: A permit differing from the consuming session in any single bound field is rejected and the mismatching field is identifiable from the diagnostic.
  AC-2: A consumed permit cannot be consumed again, including when presented with a changed nonce.
  AC-3: A second session identity cannot consume a permit already consumed for another session.
  AC-4: Undefined action bits and composite values not explicitly allowed are rejected.
  AC-5: Exhausted finite quotas or capacities produce an explicit exhaustion result.

## T025-STK-003
A validation session is created by a host-generated controller identity, is addressed by a handle bound to that controller identity and a generation, and moves only through the defined lifecycle and terminal states.
- Revision: 1
- Level: stakeholder
- Status: accepted
- Source: {"kind": "admitted_packet_and_bridge", "reference": "packet.md (session handle / lifecycle clause); interface-bridge.md REF-002; anchors: XVE-SYS-0144, XVE-SYS-0152, FR-018"}
- Applicability: T025 standalone candidate; bounded lifecycle foundation only, stimulation and Maestro triggers deferred.
- VerificationIntent: Refined by T025-SR-011..T025-SR-013 and verified by the ownership/recreation, transition-table, and ordering tests.
- AcceptanceCriteria: AC-1: Every lifecycle state declared, armed, active, closing, closed, expired, revoked, evidence-incomplete is reachable through defined operations.
  AC-2: A stale handle, a foreign handle, and a handle from a recreated controller cannot authorise an operation on another live session.
  AC-3: An unsafe repeat of an already-completed lifecycle operation is rejected deterministically.
  AC-4: Validation of handle, context, time, and action completes before any state mutation.

## T025-STK-004
Any rejected operation leaves the affected session and permit state unchanged and produces a stable, ordered diagnostic that carries no payload.
- Revision: 1
- Level: stakeholder
- Status: accepted
- Source: {"kind": "admitted_packet_and_bridge", "reference": "packet.md (rejection / diagnostics clause); interface-bridge.md REF-002; anchors: XVE-SYS-0154, FR-019, FR-020"}
- Applicability: T025 standalone candidate; payload-free diagnostic foundation, durable intent/outcome provenance deferred.
- VerificationIntent: Refined by T025-SR-015 and T025-SR-016 and verified by snapshot-equality and diagnostic-precedence tests.
- AcceptanceCriteria: AC-1: For every negative case, observable session state, permit consumption state, and counters are identical before and after the rejected call.
  AC-2: Repeating an identical rejected call produces an identical diagnostic code sequence.
  AC-3: When more than one failure applies, the reported code follows the declared precedence order deterministically.
  AC-4: No diagnostic contains a payload, item, observation, or free-form content field.

## T025-STK-005
The normal route must emit zero communication items, zero telemetry, zero network traffic, and zero persisted records.
- Revision: 1
- Level: stakeholder
- Status: accepted
- Source: {"kind": "admitted_packet", "reference": "packet.md (no emission / no transport clause); anchors: FR-020"}
- Applicability: T025 standalone candidate; emission-free foundation, no transport, gateway, listener, journal, lease, dashboard, persistent store, or external service.
- VerificationIntent: Refined by T025-SR-018 and verified by API-surface static checks plus a nominal-scenario zero-emission counter assertion.
- AcceptanceCriteria: AC-1: The candidate exposes no emission, transport, journal, or persistence API.
  AC-2: Nominal (non-test) execution performs no I/O beyond in-memory state.
  AC-3: Any normal-route emission counter reported by the candidate is zero.

## T025-STK-006
The foundation's memory, permit bookkeeping, and session capacity are finite and configurable, and concurrent use yields deterministic results without duplicate consumption.
- Revision: 1
- Level: stakeholder
- Status: accepted
- Source: {"kind": "admitted_packet_and_bridge", "reference": "packet.md (synchronization and lifetime clause); interface-bridge.md REF-002; anchors: XVE-SYS-0147, FR-033"}
- Applicability: T025 standalone candidate; finite host-configurable bounds with no invented numeric reliability target.
- VerificationIntent: Refined by T025-SR-006, T025-SR-010, T025-SR-014, T025-SR-017 and verified by boundary and concurrent stress tests.
- AcceptanceCriteria: AC-1: Session capacity, permit-consumption bookkeeping, and mapping tables have finite, host-configurable bounds with defined exhaustion behaviour.
  AC-2: Concurrent attempts to consume the same permit produce exactly one success and a deterministic set of failures.
  AC-3: Concurrent session operations do not corrupt handle/controller binding or lifecycle state.
  AC-4: Time-authority lifetime and copy/synchronisation rules are explicit and honoured.
